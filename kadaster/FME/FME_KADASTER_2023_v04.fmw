FME workspace FME_KADASTER_2023_v04.fmw

Parameters:
- DestDataset_DGNV8 = C:\EXPORT\KADASTER_ONDERGRONDEN_EXPORT   # Destination Bentley MicroStation Design File
- x_MIN_X = 250000   # Minimum X
- x_MIN_Y = 550000   # Minimum Y
- x_MAX_X = 255000   # Maximum X
- x_MAX_Y = 555000   # Maximum Y
- SourceDataset_POSTGIS_10 = PG   # Connection
- DestDataset_ACAD = C:\EXPORT\KADASTER_ONDERGRONDEN_EXPORT   # Destination Autodesk AutoCAD DWG/DXF File

Readers:
- POSTGIS_2: POSTGIS from $(SourceDataset_POSTGIS_10)

Writers:
- DGNV8_1: DGNV8 to $(DestDataset_DGNV8)
- ACAD_1: ACAD to $(DestDataset_ACAD)

ondersteunendwaterdeel (reader POSTGIS_2)
    attributes: ogc_fid serial,PrimaryKey, gml_id varchar(80), objectbegintijd varchar(10), identificatie.namespace varchar(8), identificatie.lokaalid varchar(38), tijdstipregistratie varchar(19), eindregistratie varchar(19), lv_publicatiedatum varchar(19), bronhouder varchar(5), inonderzoek bool, relatievehoogteligging int4, bgt_status varchar(8), bgt_type varchar(16), objecteindtijd varchar(10), plus_status varchar(4)
    -> Cloner_6
scheiding (reader POSTGIS_2)
    attributes: ogc_fid serial,PrimaryKey, gml_id varchar(80), objectbegintijd varchar(10), identificatie.namespace varchar(8), identificatie.lokaalid varchar(38), tijdstipregistratie varchar(19), lv_publicatiedatum varchar(19), bronhouder varchar(5), inonderzoek bool, relatievehoogteligging int4, bgt_status varchar(8), bgt_type varchar(14), objecteindtijd varchar(10), eindregistratie varchar(19), plus_type varchar(11), plus_status varchar(8)
    -> Cloner_6
waterdeel (reader POSTGIS_2)
    attributes: ogc_fid serial,PrimaryKey, gml_id varchar(80), objectbegintijd varchar(10), identificatie.namespace varchar(8), identificatie.lokaalid varchar(38), tijdstipregistratie varchar(19), lv_publicatiedatum varchar(19), bronhouder varchar(5), inonderzoek bool, relatievehoogteligging int4, bgt_status varchar(8), bgt_type varchar(20), objecteindtijd varchar(10), eindregistratie varchar(19), plus_type varchar(23), plus_status varchar(4)
    -> Cloner_6
wegdeel (reader POSTGIS_2)
    attributes: ogc_fid serial,PrimaryKey, gml_id varchar(80), objectbegintijd varchar(10), identificatie.namespace varchar(8), identificatie.lokaalid varchar(38), tijdstipregistratie varchar(19), lv_publicatiedatum varchar(19), bronhouder varchar(5), inonderzoek bool, relatievehoogteligging int4, bgt_status varchar(8), bgt_functie varchar(22), optalud bool, bgt_fysiekvoorkomen varchar(19), plus_fysiekvoorkomen varchar(17), eindregistratie varchar(19), objecteindtijd varchar(10), plus_functie varchar(21), plus_status varchar(4)
    -> Cloner_6
ondersteunendwegdeel (reader POSTGIS_2)
    attributes: ogc_fid serial,PrimaryKey, gml_id varchar(80), objectbegintijd varchar(10), identificatie.namespace varchar(8), identificatie.lokaalid varchar(38), tijdstipregistratie varchar(19), eindregistratie varchar(19), lv_publicatiedatum varchar(19), bronhouder varchar(5), inonderzoek bool, relatievehoogteligging int4, bgt_status varchar(8), optalud bool, bgt_functie varchar(14), bgt_fysiekvoorkomen varchar(19), plus_fysiekvoorkomen varchar(22), objecteindtijd varchar(10), plus_status varchar(4)
    -> Cloner_6
Cloner_6
    COPIES = 1
    COPYATT = _copynum
    COPY -> Cloner_4
AttributeKeeper_8
    CREATE_BULK_MODE_FEATURES = No
    -> AttributeCreator
AttributeCreator
    ATTR_TABLE = SET_TO LAAGNAAM = Topo
    -> Cloner_2
bag_light_export_pand (reader POSTGIS_2)
    attributes: ogc_fid serial,PrimaryKey, gml_id varchar(80), feature_id numeric(20,0), rdf_seealso varchar(80), identificatie varchar(80), bouwjaar numeric(20,0), status varchar(80), gebruiksdoel varchar(80), oppervlakte_min numeric(20,0), oppervlakte_max numeric(20,0), aantal_verblijfsobjecten numeric(20,0)
    -> Cloner_5
TopologyBuilder_4
    ALLOW_CYCLES = No
    BOUNDING_EDGES = All
    CLEANING_TOLERANCE = None
    CLEAN_DATA = No
    DEAGGREGATE_INPUT = Yes
    MAX = 0
    OVERLAPPING_MODE = No
    PROP_ATTRS = No
    LINE -> AttributeKeeper_7
AttributeKeeper_7
    CREATE_BULK_MODE_FEATURES = No
    -> AttributeCreator_10
AttributeCreator_10
    ATTR_TABLE = SET_TO LAAGNAAM = Topo_pand
    -> Cloner_2
openbareruimtelabel (reader POSTGIS_2)
    attributes: ogc_fid serial,PrimaryKey, gml_id varchar(80), objectbegintijd varchar(10), identificatie.namespace varchar(8), identificatie.lokaalid varchar(38), tijdstipregistratie varchar(19), lv_publicatiedatum varchar(19), bronhouder varchar(5), inonderzoek bool, relatievehoogteligging int4, bgt_status varchar(8), identificatiebagopr int8, openbareruimtenaam.tekst varchar(55), openbareruimtenaam.positie_1.hoek float8, openbareruimtetype varchar(22), openbareruimtenaam.positie_2.hoek float8, openbareruimtenaam.positie_3.hoek float8, eindregistratie varchar(19), objecteindtijd varchar(10), plus_status varchar(4)
    -> AttributeCreator_8
AttributeCreator_8
    ATTR_TABLE:
      SET_TO igds_type = igds_text
      SET_TO igds_text_string = @Value(openbareruimtenaam.tekst)
      SET_TO igds_rotation = 0
      SET_TO igds_textstyle_id = 3
      SET_TO igds_text_size = 2.00
      SET_TO autocad_text_rotation = 0
      SET_TO autocad_text_size = 2
      SET_TO autocad_text_string = @Value(openbareruimtenaam.tekst)
    -> AttributeKeeper_5
AttributeKeeper_5
    CREATE_BULK_MODE_FEATURES = NO
    KEEP_ATTRS = autocad_text_rotation,autocad_text_size,autocad_text_string,igds_rotation,igds_text_size,igds_text_string,igds_textstyle_id,igds_type
    -> AttributeCreator_9
AttributeCreator_9
    ATTR_TABLE = SET_TO LAAGNAAM = Straatnaam
    -> Cloner
buildingpart (reader POSTGIS_2)
    attributes: ogc_fid serial,PrimaryKey, gml_id varchar(80), creationdate varchar(10), lv_publicatiedatum varchar(19), relatievehoogteligging int4, inonderzoek bool, tijdstipregistratie varchar(23), namespace varchar(8), lokaalid varchar(38), bronhouder varchar(5), bgt_status varchar(8), plus_status varchar(10), identificatiebagpnd int8, tekst text, hoek text, identificatiebagvbolaagstehuisnummer text
    -> GeometryFilter_4
GeometryFilter_4
    BREAK_AGG = No
    GEOM_PORT_NAMES = Point Line Arc Area Ellipse Text Raster "Point Cloud" Surface Solid Collection Null Instance
    POINT -> StringReplacer
StringReplacer
    CASE = NO
    FIND_TEXT = {
    NO_MATCH = _FME_NO_OP_
    REGEXP = NO
    SRC_ATTRS = tekst
    -> StringReplacer_2
StringReplacer_2
    CASE = NO
    FIND_TEXT = }
    NO_MATCH = _FME_NO_OP_
    REGEXP = NO
    SRC_ATTRS = tekst
    -> AttributeCreator_11
AttributeCreator_11
    ATTR_TABLE:
      SET_TO igds_type = igds_text
      SET_TO igds_text_string = @Value(tekst)
      SET_TO igds_rotation = 0
      SET_TO igds_textstyle_id = 3
      SET_TO igds_text_size = 2.00
      SET_TO autocad_text_rotation = 0
      SET_TO autocad_text_size = 2
      SET_TO autocad_text_string = @Value(tekst)
    -> AttributeKeeper_4
AttributeKeeper_4
    CREATE_BULK_MODE_FEATURES = NO
    KEEP_ATTRS = autocad_text_rotation,autocad_text_size,autocad_text_string,igds_rotation,igds_text_size,igds_text_string,igds_textstyle_id,igds_type,tekst
    -> AttributeCreator_12
AttributeCreator_12
    ATTR_TABLE = SET_TO LAAGNAAM = Huisnummer_tekst
    -> Cloner
Cloner
    COPIES = 1
    COPYATT = _copynum
    COPY -> Cloner_2
kadastralegrens (reader POSTGIS_2)
    attributes: ogc_fid serial,PrimaryKey, gml_id varchar(80), begingeldigheid varchar(23), tijdstipregistratie varchar(23), volgnummer int4, code varchar(1), waarde varchar(6), namespace varchar(24), lokaalid int4, typegrens|typegrens|code int4, typegrens|typegrens|waarde varchar(14), perceellinks|namespace varchar(25), perceellinks|lokaalid int8, perceelrechts|namespace varchar(25), perceelrechts|lokaalid int8
    -> AttributeKeeper
AttributeKeeper
    CREATE_BULK_MODE_FEATURES = No
    -> Matcher
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCH_STRATEGY = Match Selected Attributes
    SINGLE_MATCHED -> LineOnLineOverlayer [LINE]
    NOT_MATCHED -> LineOnLineOverlayer [LINE]
LineOnLineOverlayer
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    LINE -> AttributeKeeper_6
AttributeKeeper_6
    CREATE_BULK_MODE_FEATURES = No
    -> AttributeCreator_4
AttributeCreator_4
    ATTR_TABLE = SET_TO LAAGNAAM = Grens_bestaand
    -> Cloner_2
Cloner_2
    COPIES = 1
    COPYATT = _copynum
    COPY -> Tester
StringConcatenator
    ACTION = Create New Attribute
    PARM_LINE = fme_basicstring:17%1%17:@Value(_substr_X)_@Value(_substr_Y)
    VAL_ATTR = bestandsnm
    -> Cloner_3
Cloner_3
    COPIES = 1
    COPYATT = _copynum
    COPY -> DGNStyler_5
    COPY -> GeometryFilter_5
DGNStyler_5
    COLOR_BY_LEVEL_DISPLAY = Yes (V8 Only)
    COLOR_CHOICE_DISPLAY = RGB
    LINE_STYLE = 0
    LINE_WEIGHT = ByLevel
    TEXT_JUSTIFICATION = Center Center
    DGNStyled -> Bebouwing (writer DGNV8_1)
Bebouwing (writer DGNV8_1)
GeometryFilter_5
    BREAK_AGG = No
    GEOM_PORT_NAMES = Point Line Arc Area Ellipse Text Raster "Point Cloud" Surface Solid Collection Null Instance
    POINT -> LabelPointReplacer
    LINE -> public.kadastralegrens00 (writer ACAD_1)
LabelPointReplacer
    ALWAYSROTATE = no
    HEIGHT = 2
    LABATTR = @Value(autocad_text_string)
    LabelPoint -> public.kadastralegrens00 (writer ACAD_1)
public.kadastralegrens00 (writer ACAD_1)

Bookmark: filter + validatie + topology
Cloner_4
    COPIES = 1
    COPYATT = _copynum
    COPY -> AttributeKeeper_3
AttributeKeeper_3
    CREATE_BULK_MODE_FEATURES = No
    -> GeometryFilter_2
GeometryFilter_2
    BREAK_AGG = No
    GEOM_PORT_NAMES = Point Line Arc Area Ellipse Text Raster "Point Cloud" Surface Solid Collection Null Instance
    LINE -> GeometryValidator_2
    ARC -> GeometryValidator_2
    AREA -> GeometryValidator_2
    ELLIPSE -> GeometryValidator_2
GeometryValidator_2
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> TopologyBuilder_3
    REPAIRED -> TopologyBuilder_3
TopologyBuilder_3
    ALLOW_CYCLES = No
    BOUNDING_EDGES = All
    CLEANING_TOLERANCE = None
    CLEAN_DATA = No
    DEAGGREGATE_INPUT = Yes
    MAX = 0
    OVERLAPPING_MODE = No
    PROP_ATTRS = No
    LINE -> AttributeKeeper_8

Bookmark: Zelfde als bij de rest van de BGT - filter + validatie + topology
Cloner_5
    COPIES = 1
    COPYATT = _copynum
    COPY -> AttributeKeeper_2
AttributeKeeper_2
    CREATE_BULK_MODE_FEATURES = No
    -> GeometryFilter_3
GeometryFilter_3
    BREAK_AGG = No
    GEOM_PORT_NAMES = Point Line Arc Area Ellipse Text Raster "Point Cloud" Surface Solid Collection Null Instance
    LINE -> GeometryValidator_4
    ARC -> GeometryValidator_4
    AREA -> GeometryValidator_4
GeometryValidator_4
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> TopologyBuilder_4
    REPAIRED -> TopologyBuilder_4

Bookmark: De niet 6 cijferige X waarden aanpassen met een voorloop-0
Note: Voorloop NUL nodig?
Tester
    BOOL_OP = OR
    TEST_CLAUSE = TEST $(x_MIN_X) < 100000
    TEST_MODE = TEST
    PASSED -> SubstringExtractor_4
    FAILED -> SubstringExtractor_3
Note: XMIN :: VOORLOOP NUL ! 2 cijfers !
SubstringExtractor_4
    END = 1
    RESULT_ATTR = _x_waarde_temp
    SRC_STRING = $(x_MIN_X)
    START = 0
    -> StringConcatenator_6
Note: 0 er voor !
StringConcatenator_6
    ACTION = Create New Attribute
    PARM_LINE = 0@Value(_x_waarde_temp)
    VAL_ATTR = _substr_X
    -> SubstringExtractor_2
Note: XMIN :: 3 cijfers
SubstringExtractor_3
    END = 2
    RESULT_ATTR = _substr_X
    SRC_STRING = $(x_MIN_X)
    START = 0
    -> SubstringExtractor_2
Note: YMIN :: 3 cijfers
SubstringExtractor_2
    END = 2
    RESULT_ATTR = _substr_Y
    SRC_STRING = $(x_MIN_Y)
    START = 0
    -> StringConcatenator
